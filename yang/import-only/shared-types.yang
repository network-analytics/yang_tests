module shared-types {
  yang-version 1.1;

  namespace "urn:test:shared-types";
  prefix st;

  revision 2026-07-18;

  typedef port-number {
    type uint16 {
      range "1..65535";
    }
  }

  container shared-root {
    leaf internal-value {
      type string;
    }
  }
}
