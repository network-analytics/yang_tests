module xpath-test {
  yang-version 1.1;
  namespace "urn:xpath:test";
  prefix xt;

  container "top-container" {
    container "child-container" {
      leaf "value1" { type string; }
      leaf "value2" { type uint8; }
    }
  }

  container "anydata-container" {
    container "child-container" {
        leaf "value1" { type string; }
        anydata "payload";
    }
  }

}
