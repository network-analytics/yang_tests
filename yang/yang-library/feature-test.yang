module feature-test {
  yang-version 1.1;
  namespace "urn:test:feature";
  prefix ft;

  revision 2026-04-29;

  feature advanced;

  container root {
    leaf id {
      type string;
    }

    leaf advanced-value {
      if-feature advanced;
      type string;
    }
  }
}
